;; add (princ) to properly cleanup command and avoid context leaks in application-level commands
;; autocad-ballet
(defun c:q` () (command "invoke-addin-command") (princ))
(defun c:qq` () (command "invoke-last-addin-command") (princ))
(defun c:ww () (command "switch-view") (princ))
(defun c:wwl () (command "switch-layout") (princ))
(defun c:wd () (command "switch-document") (princ))
(defun c:wwd () (command "switch-document") (princ))
(defun c:we () (command "switch-view-last") (princ))
(defun c:wr () (command "switch-view-recent") (princ))
(defun c:wwr () (command "switch-view-recent") (princ))
(defun c:fse () (command "filter-selection-elements") (princ))
(defun c:fses () (command "filter-selection-elements-span") (princ))
(defun c:scv () (command "select-by-categories-in-view") (princ))
(defun c:scd () (command "select-by-categories-in-document") (princ))
(defun c:scs () (command "select-by-categories-in-session") (princ))
(defun c:slv () (command "select-by-layers-in-view") (princ))
(defun c:sld () (command "select-by-layers-in-document") (princ))
(defun c:sls () (command "select-by-layers-in-session") (princ))
(defun c:ssc () (command "select-by-same-layers-of-selected-in-view") (princ))
(defun c:sscv () (command "select-by-same-layers-of-selected-in-view") (princ))
(defun c:sscd () (command "select-by-same-layers-of-selected-in-document") (princ))
(defun c:sscs () (command "select-by-same-layers-of-selected-in-session") (princ))
(defun c:ssl () (command "select-by-same-layers-of-selected-in-view") (princ))
(defun c:sslv () (command "select-by-same-layers-of-selected-in-view") (princ))
(defun c:ssld () (command "select-by-same-layers-of-selected-in-document") (princ))
(defun c:ssls () (command "select-by-same-layers-of-selected-in-session") (princ))
(defun c:fv () (command "filter-selection-in-view") (princ))
(defun c:fd () (command "filter-selection-in-document") (princ))
(defun c:fs () (command "filter-selection-in-session") (princ))
(defun c:orw () (command "open-documents-recent-read-write") (princ))
(defun c:orr () (command "open-documents-recent-read-only") (princ))
(defun c:et () (command "edit-selected-text-in-view") (princ))
(defun c:etv () (command "edit-selected-text-in-view") (princ))
(defun c:ets () (command "edit-selected-text-in-session") (princ))
(defun c:zs () (c:zoom-selected))
(defun c:saf () (command "save-all-force"))
(defun c:wc () (command "close" "y") (princ))
(defun c:wcc () (command "kill-current-process"))
(defun c:ih () (command "isolate-hide-on-new-layer") (princ))
(defun c:uih () (command "unisolate-hide-on-new-layer") (princ))
(defun c:il () (command "isolate-lock-on-new-layer") (princ))
(defun c:uil () (command "unisolate-lock-on-new-layer") (princ))
(defun c:rro () (command "reopen-documents-read-only") (princ))
(defun c:rrw () (command "reopen-documents-read-write") (princ))
(defun c:tg () (command "tag-selected-in-view") (princ))
(defun c:tgv () (command "tag-selected-in-view") (princ))
(defun c:tgd () (command "tag-selected-in-document") (princ))
(defun c:tgs () (command "tag-selected-in-session") (princ))
(defun c:ssd () (command "select-similar-in-document") (princ))
(defun c:sss () (command "select-similar-in-session") (princ))
(defun c:stv () (command "select-by-tags-in-view") (princ))
(defun c:stgv () (command "select-by-tags-in-view") (princ))
(defun c:stgd () (command "select-by-tags-in-document") (princ))
(defun c:stgs () (command "select-by-tags-in-session") (princ))
(defun c:sfv () (command "select-by-selection-filters-in-view") (princ))
(defun c:sfd () (command "select-by-selection-filters-in-document") (princ))
(defun c:sfs () (command "select-by-selection-filters-in-session") (princ))
(defun c:satv () (command "select-by-tags-of-selected-in-view") (princ))
(defun c:sat () (command "select-by-tags-of-selected-in-view") (princ))
(defun c:sstv () (command "select-by-same-tags-of-selected-in-view") (princ))
(defun c:sst () (command "select-by-same-tags-of-selected-in-view") (princ))
(defun c:ctg () (command "copy-tags-from-selection-in-view") (princ))
(defun c:aat () (command "align-selected-in-view-top") (princ))
(defun c:aar () (command "align-selected-in-view-right") (princ))
(defun c:aal () (command "align-selected-in-view-left") (princ))
(defun c:aab () (command "align-selected-in-view-bottom") (princ))
(defun c:aach () (command "align-selected-in-view-center-horizontal") (princ))
(defun c:aacv () (command "align-selected-in-view-center-vertical") (princ))
(defun c:dtv () (command "delete-tags-in-view") (princ))
(defun c:dtd () (command "delete-tags-in-document") (princ))
(defun c:dts () (command "delete-tags-in-session") (princ))

;; regular autocad
(defun c:fss () (command "refclose" "save") (princ))
(defun c:rs () (command "refset") (princ))
(defun c:rsa () (command "refset" "add") (princ))
(defun c:rsr () (command "refset" "remove") (princ))
(defun c:rf () (command "-refedit" "ok" "all" "no") (princ))
(defun c:sv () (command ".selectsimilar") (princ))
(defun c:ssv () (command ".selectsimilar") (princ))
(defun c:pii () (command "pickstyle") (princ))
(defun c:cc () (command "lay-cur") (princ))
(defun c:chh () (command "change-color") (princ))
(defun c:ze () (command "zoom" "extents") (princ))
(defun c:cbb () (command "copybase" "0,0,0") (princ))
(defun c:ccb () (command "cutbase" "0,0,0") (princ))
(defun c:cbb () (command "copybase" "0,0,0") (princ))
(defun c:pbb () (command "pasteclip" "0,0,0") (princ))
(defun c:hh () (command "hideobjects") (princ))
(defun c:ii () (command "isolateobjects") (princ))
(defun c:jj () (command "lay-mcur-make-object-layer-current") (princ))
(defun c:uu () (command "unisolateobjects") (princ))
(defun c:dps () (command "toggle-display-plot-styles") (princ))
(defun c:ss () (command "_.pselect" "_p" "") (princ))
(defun c:bf () (command "draworder" "front") (princ))
(defun c:sb () (command "draworder" "back") (princ))
;; needed until i find out why ctrl+double click no longer edits block attributes in-place
(defun c:at () (command "attipedit") (princ))
(defun c:fr () (command "layfrz") (princ))
(defun c:gg () (setvar "pickstyle" (- 1 (getvar "pickstyle"))) (princ))
(defun c:tv () (command "-vports" "toggle") (princ))
(defun c:lu () (command "layulk") (princ))
(defun c:hgb () (command "hatchgenerateboundary") (princ))
(defun c:ug () (command "ungroup") (princ))
(defun c:xrr () (command "xrefreload") (princ))
